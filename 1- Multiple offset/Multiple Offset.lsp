(princ "Author: Ahmed Abd-elmotey - Jan 2016 - ahmed.abdelmotey92@gmail.com - To Run Type : MOF")
(defun c:mof()
	(vl-load-com)
	(setq offmeasure (getreal "\nEnter Offset Distance"))
	(initget 1 "Outside Center Inside")(setq oftype (getkword "\nChose Offset Type [Outside/Center/Inside]"))
	(initget 1 "Yes NO")(setq ans (getkword "\nDelete Source Polyline ? [Yes/No]"))
	(if (setq s (ssget))
        (progn
            (setq i (1- (sslength s)))
            (while (<= 0 i) 
                (setq e (vlax-Ename->Vla-Object (ssname s i)) i (1- i))
				(cond 
					((= oftype "Outside")(vla-offset e offmeasure))
					((= oftype "Center")(progn (vla-offset e offmeasure)(vla-offset e (* -1 offmeasure))))
					((= oftype "Inside")(vla-offset e (* -1 offmeasure)))
				)
				(if (= ans "Yes") (vla-delete e))
            )
        )
    )
)
